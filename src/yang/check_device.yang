module check_device {

    namespace "http://example.com/check_device";
    prefix check_device;

    import ietf-inet-types {
        prefix inet;
    }
    import tailf-common {
        prefix tailf;
    }
    import tailf-ncs {
        prefix ncs;
    }

    description
      "Simple example of how to check operationnal data on a device with PyATS";

    revision 2016-01-01 {
        description
          "Initial revision.";
    }

    container check_device {
        tailf:action check_version {
            tailf:info "Check if device config is according to MES step";
            tailf:actionpoint check_device_check_version;
            input {
                leaf device {
                    type leafref{
                        path "/ncs:devices/ncs:device/ncs:name";
                    }
                    mandatory true;
                }
                leaf target_version {
                    type string;
                    mandatory true;
                }
            }
            output {

                leaf device {
                     type string;
                }

                leaf current_version {
                    type string;
                }

                leaf operating_system {
                    type string;
                }

                leaf check_status {
                   type enumeration{
                        enum "OK";
                        enum "NOK";
                        enum "ERROR";
                    }
                }
                leaf check_message {
                    type string;
                }
            }
        }

        tailf:action run_command {
            tailf:info "Run the show command on the device";
            tailf:actionpoint check_device_run_command;
            input {
                leaf device {
                    type leafref{
                        path "/ncs:devices/ncs:device/ncs:name";
                    }
                    mandatory true;
                }
                leaf show_command {
                    type string;
                    mandatory true;
                }
            }
            output {

                leaf device {
                     type string;
                }

                leaf json {
                    type string;
                }

                leaf raw {
                    type string;
                }

                leaf has_error {
                    type boolean;
                }
            }
        }
    }
}
